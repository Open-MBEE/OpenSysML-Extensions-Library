library package DocumentQueries {
	/* NON-NORMATIVE OpenSysML document-query vocabulary;
	 * not part of the OMG SysML or KerML standard library. */

	private import KerML::Root::Element;
	private import ScalarValues::*;

	abstract calc def Query {
		return result : Element[0..*] ordered;
	}

	calc def OwnedElements {
		in source : Element[0..*] ordered;
		return result : Element[0..*] ordered;
	}

	/* Descendants and Ancestors walk ownership from source to maxDepth levels;
	 * maxDepth = null (the default) walks the whole tree. Descendants walks the
	 * owned members of each namespace; relationships = true walks ownership as
	 * KerML 8.3.2.1 defines it instead — ownedRelationship, then the related
	 * elements each relationship owns — so the memberships, specializations,
	 * typings, feature values and the implicit elements they own are reached. */
	calc def Descendants {
		in source : Element[0..*] ordered;
		in maxDepth : Integer[0..1] default null;
		in relationships : Boolean[0..1] default false;
		return result : Element[0..*] ordered;
	}

	calc def Ancestors {
		in source : Element[0..*] ordered;
		in maxDepth : Integer[0..1] default null;
		return result : Element[0..*] ordered;
	}

	/* Named: the model elements the qualified names denote, in the order given;
	 * a name that denotes nothing is an error. */
	calc def Named {
		in qualifiedName : String[1..*] ordered;
		return result : Element[0..*] ordered;
	}

	/* Objects: the objects the session holds that are of the named type,
	 * each nested object under its path (`car.wheels[2]`). Requires a session. */
	calc def Objects {
		in type : String[1];
		return result : Element[0..*] ordered;
	}

	/* Verdicts: one row per assertion checked on each source row's object and the
	 * objects it holds (a session object as it stands, an element as declared);
	 * kind selects all, constraint, requirement, satisfaction or verification. */
	calc def Verdicts {
		in source : Element[0..*] ordered;
		in kind : String[1] default "all";
		return result : Element[0..*] ordered;
	}

	/* The properties of a Verdicts row, for Project and column expressions
	 * (`Verdict::verdict`); a row also answers its assertion's own properties by
	 * name. */
	attribute def Verdict {
		ref assertion : Element[1];
		attribute kind : String[1];
		ref carrier : Element[0..1];
		attribute path : String[1];
		attribute verdict : String[1];
		attribute condition : String[0..1];
		attribute reason : String[0..1];
		attribute 'verification' : String[0..*] ordered;
	}

	/* States: one row per active leaf state of each source row's object (a
	 * session object, or an element whose objects the session holds), machines
	 * in the object's order and leaves in region order; an object with no state
	 * machine is refused. Requires a session. */
	calc def States {
		in source : Element[0..*] ordered;
		return result : Element[0..*] ordered;
	}

	/* InState: the objects the session holds whose state machine is in the
	 * named state, a leaf or a state enclosing one, by name or dotted path
	 * (`on.run`); a name no machine declares is refused. Requires a session. */
	calc def InState {
		in name : String[1];
		return result : Element[0..*] ordered;
	}

	/* The properties of a States row, for Project and column expressions
	 * (`State::name`); a row also answers its state declaration's own
	 * properties. object and 'state' are elements: project them by name. */
	attribute def State {
		ref object : Element[1];
		attribute path : String[1];
		attribute machine : String[1];
		attribute name : String[1];
		attribute statePath : String[1];
		ref 'state' : Element[0..1];
		attribute region : String[1];
		attribute enclosing : String[0..*] ordered;
	}

	/* Events: the session's trace as a relation in the order recorded, one row
	 * per accept, send, transition fired, state entry, exit or do step, choice
	 * point drawn or guard left unevaluated; source keeps the rows of the given
	 * objects (every object when null), kind the kinds named (`all`, or kinds
	 * separated by `,`), since and before the instants in [since, before) as
	 * durations or bare numbers of the clock's seconds. Requires a session
	 * recording a trace. */
	calc def Events {
		in source : Element[0..*] ordered default null;
		in kind : String[1] default "all";
		in since : ScalarValue[0..1] default null;
		in before : ScalarValue[0..1] default null;
		return result : Element[0..*] ordered;
	}

	/* The properties of an Events row, for Project and column expressions
	 * (`Event::time`, `Event::'event'`); a row also answers the properties of
	 * the behavior that made it. object and target are elements: project them
	 * by name. */
	attribute def Event {
		attribute kind : String[1];
		attribute time : ScalarValue[1];
		ref object : Element[0..1];
		attribute path : String[0..1];
		attribute machine : String[0..1];
		attribute 'state' : String[0..1];
		attribute 'from' : String[0..1];
		attribute 'to' : String[0..1];
		ref target : Element[0..1];
		attribute 'event' : String[0..1];
		attribute payload : String[0..*] ordered;
		attribute alternatives : String[0..*] ordered;
		attribute taken : String[0..1];
		attribute text : String[1];
	}

	calc def RelatedElements {
		in source : Element[0..*] ordered;
		/* relationshipKind: "specialization", "subsetting", "redefinition",
		 * "typing", "connection", "allocation", "satisfaction", "verification",
		 * "derivation" or "refinement"; direction: "outgoing" or "incoming". */
		in relationshipKind : String[1];
		in direction : String[1];
		/* maxDepth: how many relationships to follow; null (the default) is unbounded. */
		in maxDepth : Integer[0..1] default null;
		return result : Element[0..*] ordered;
	}

	/* WhereType keeps the elements that are of any of the named types: a metaclass
	 * (PartUsage) or a definition/usage of the model, subtypes included. */
	calc def WhereType {
		in source : Element[0..*] ordered;
		in type : String[1..*] ordered;
		/* exact = true keeps only the elements whose own metaclass is one of the named
		 * ones, neither its subclasses nor the model's types: the reflective walk. */
		in exact : Boolean[1] default false;
		return result : Element[0..*] ordered;
	}

	/* WhereMetadata keeps the elements annotated with any of the named metadata definitions. */
	calc def WhereMetadata {
		in source : Element[0..*] ordered;
		in 'metadata' : String[1..*] ordered;
		return result : Element[0..*] ordered;
	}

	calc def WhereName {
		in source : Element[0..*] ordered;
		in operator : String[1];
		in value : String[1];
		return result : Element[0..*] ordered;
	}

	/* WhereText keeps the projected rows whose text in any of the named columns — every column when none is named — satisfies the comparison. */
	calc def WhereText {
		in source : Element[0..*] ordered;
		in columns : String[0..*] ordered = null;
		in operator : String[1];
		in value : String[1];
		return result : Element[0..*] ordered;
	}

	calc def WhereFeature {
		in source : Element[0..*] ordered;
		in 'feature' : String[1];
		in operator : String[1];
		in value : String[1];
		/* As for Project: an element lacking the feature is a path error unless tolerated. */
		in tolerate : Boolean[1] default false;
		return result : Element[0..*] ordered;
	}

	calc def OrderBy {
		in source : Element[0..*] ordered;
		in property : String[1];
		in direction : String[1];
		in missing : String[1];
		in multiple : String[1];
		return result : Element[0..*] ordered;
	}

	/* Distinct: seq without its repeated values, the first of each kept in the
	 * order met; a cell applies it to a sequence as `->DocumentQueries::Distinct()`
	 * beside the KerML sequence functions (`->SequenceFunctions::size()`,
	 * `->ControlFunctions::select {in e; …}`). */
	calc def Distinct {
		in seq : Base::Anything[0..*] ordered nonunique;
		return result : Base::Anything[0..*] ordered;
	}

	/* One computed table column: exactly one of expression, cell, or path.
	 * expression is evaluated in query scope; cell receives each row as its
	 * parameter; path reads a dotted member path from the row. */
	attribute def ColumnSpec;

	/* A cell reads row properties through its typed row parameter
	 * (e.g. row.mass); an expression uses query-scope features such as
	 * Subsystem::mass. Both support +, -, *, / arithmetic,
	 * string concatenation with +, and ?? for absent-value defaults.
	 * A feature chain (e.g. stat.runs or 'Monte Carlo'.runs) reads a
	 * feature of a member nested in the row element, each segment
	 * resolved against the members of the element reached so far —
	 * own members before inherited ones, else the element-valued
	 * metaclass feature of that name (type.documentation reads the
	 * documentation of a usage's definition); a row lacking a segment
	 * is absent on that row, a member declaring no value is an empty
	 * cell, and a member holding more values than its multiplicity
	 * admits fails the column as a direct feature column does. A cell
	 * over a metadata row reads its direct features only. A property
	 * string of Project's properties or OrderBy's property may hold
	 * the same path ("stat.runs").
	 * A row not conforming to the feature's declaring type reads it as
	 * absent; a failing expression, an absent result not defaulted
	 * with ??, or a multi-valued result fails the query with a typed
	 * error naming the row and column. */
	calc def Column {
		in name : String[1];
		in expression : ScalarValue[0..1];
		in calc cell[0..1] { in row : Base::Anything[1]; return : ScalarValue[0..1]; }
		in path : String[0..1];
		return result : ColumnSpec[1];
	}

	calc def Project {
		in source : Element[0..*] ordered;
		in properties : String[0..*] ordered default null;
		in columns : ColumnSpec[0..*] ordered default null;
		/* A property an element row lacks — a feature name, or a dotted member path
		 * whose segment names no member on that row — is a path error naming the
		 * element and the features it does have; tolerate = true keeps the empty
		 * cell. A Column path is a computed cell and stays absent, as documented above. */
		in tolerate : Boolean[1] default false;
		return result : Element[0..*] ordered;
	}

	abstract part def Document {
		attribute title : String[1];
	}

	abstract part def Section {
		attribute title : String[1];
	}

	abstract part def ContentBlock;

	part def Paragraph :> ContentBlock {
		attribute text : String[0..1];
	}

	/* Inline runs compose a paragraph in declaration order, joined by
	 * single spaces. */
	abstract part def Run;

	part def Span :> Run {
		attribute text : String[1];
		/* style: "plain", "emphasis", "strong", "code" or "math"; a math
		 * span's text is LaTeX, typeset inline. */
		attribute style : String[0..1];
	}

	part def Link :> Run {
		attribute text : String[1];
		attribute target : String[1];
	}

	/* Ref links to a named content block of this or another document, to
	 * another document itself, or to a model element outside every document
	 * (a usage by name, any element as `E.metadata`); text defaults to the
	 * target's title, caption or name. */
	part def Ref :> Run {
		attribute text : String[0..1];
		ref target : Element[1];
	}

	/* Column runs style a query-backed paragraph's or list's text: each
	 * result row renders one run per column run, in declaration order. */
	abstract part def ColumnRun;

	part def SpanColumn :> ColumnRun {
		/* column: the projected column whose values become the run text. */
		attribute column : String[1];
		/* style: "plain", "emphasis", "strong", "code" or "math". */
		attribute style : String[0..1];
		/* styleColumn: a projected column supplying each row's style. */
		attribute styleColumn : String[0..1];
	}

	part def LinkColumn :> ColumnRun {
		/* column: the projected column whose values become the link text. */
		attribute column : String[1];
		/* targetColumn: a projected column supplying each row's one link
		 * destination. */
		attribute targetColumn : String[1];
	}

	part def Table :> ContentBlock {
		attribute caption : String[0..1];
		/* groupBy: a projected column name; rows are grouped by its value
		 * into subtables in order of first appearance. */
		attribute groupBy : String[0..1];
		/* columnWidths: the relative widths of the projected columns in order,
		 * in the source's units; 0 sizes a column automatically. Renderers
		 * honour them proportionally. */
		attribute columnWidths : Integer[0..*] ordered nonunique;
		/* columnLabels: the headings of the projected columns in order, where
		 * they differ from the column names; "" heads a column by its name. */
		attribute columnLabels : String[0..*] ordered nonunique;
	}

	part def List :> ContentBlock {
		attribute style : String[0..1];
	}

	/* Definitions renders each row of its query as one term with its
	 * description(s): prose from the model rather than a table of it. */
	part def Definitions :> ContentBlock {
		/* term: the projected column whose value names each entry. */
		attribute term : String[1];
		/* description: the projected column whose values describe it. */
		attribute description : String[1];
	}

	/* Formula typesets one LaTeX expression as display mathematics on a line
	 * of its own; a named formula is a Ref target. */
	part def Formula :> ContentBlock {
		attribute source : String[1];
		attribute caption : String[0..1];
	}

	/* Image shows an image file: location is a path relative to the document's
	 * source file, or an http(s)/file URL; alt is its text alternative. */
	part def Image :> ContentBlock {
		attribute location : String[1];
		attribute caption : String[0..1];
		attribute alt : String[0..1];
	}

	part def Diagram :> ContentBlock {
		attribute caption : String[0..1];
		/* kind: a supported rendering kind ("tree", "interconnection",
		 * "state", "action", "table" or "sequence"); required when source
		 * is a plain element, stated by the view when source is a view. */
		attribute kind : String[0..1];
		/* direction: "TB", "LR", "RL" or "BT", for kinds drawn as graphs. */
		attribute direction : String[0..1];
		/* palette: "okabe-ito", "tol-bright", "tol-muted", "tol-light",
		 * "brewer-set2", "brewer-dark2", "viridis" or "cividis"; fills the
		 * nodes of a DOT or PlantUML diagram by keyword family, black and white
		 * when absent. */
		attribute palette : String[0..1];
		/* ports: "minimal" or "full"; how much of a part's ports an
		 * interconnection diagram draws — those its connectors end at, each a
		 * small square on the part's border named beside it, or every port,
		 * labelled name : Type. Minimal when absent. */
		attribute ports : String[0..1];
		/* show: the optional notation elements the diagram draws besides those
		 * its view's rendering shows, comma-separated: "parameter-symbols",
		 * "port-symbols", "compartments", "edge-labels", "keywords",
		 * "multiplicities", "typings", "qualifiers", or "all". */
		attribute show : String[0..1];
		/* overlay: "verdicts", for a requirement diagram: runs the verification
		 * cases verifying each requirement and colours and labels it by their
		 * verdicts. Purely structural when absent. */
		attribute overlay : String[0..1];
		ref source : Element[0..1];
	}

	/* A relationship-derived Project column: the elements RelatedElements
	 * reaches from each row, as a "list" (default), a "count" or "any";
	 * maxDepth = null is unbounded, and targets, when given, keeps only the
	 * reached elements among them. */
	calc def RelatedColumn {
		in name : String[1];
		in relationshipKind : String[1];
		in direction : String[1];
		in maxDepth : Integer[0..1] default null;
		in aggregate : String[1] default "list";
		in targets : Element[0..*] ordered default null;
		return result : ColumnSpec[1];
	}

	/* WhereRelated: the source rows with at least one element reachable by the
	 * relationship kind and direction of RelatedElements within maxDepth
	 * (exists = true), or with none (exists = false); maxDepth = null is unbounded. */
	calc def WhereRelated {
		in source : Element[0..*] ordered;
		in relationshipKind : String[1];
		in direction : String[1];
		in maxDepth : Integer[0..1] default null;
		in exists : Boolean[1] default true;
		return result : Element[0..*] ordered;
	}

	/* Except: the source rows whose element, object, verdict, state or event
	 * is not among exclude, once each in source order. */
	calc def Except {
		in source : Element[0..*] ordered;
		in exclude : Element[0..*] ordered;
		return result : Element[0..*] ordered;
	}

	/* Union: the source rows, then the rows of other not already present, in
	 * order with duplicates removed. */
	calc def Union {
		in source : Element[0..*] ordered;
		in other : Element[0..*] ordered;
		return result : Element[0..*] ordered;
	}

	/* Differ: one row (key, column of left, column of right) per key value present
	 * in both left and right whose column cells differ — a keyed value comparison;
	 * keys on one side only are Except's. A key value carried by two rows on one
	 * side is a model error. */
	calc def Differ {
		in left : Element[0..*] ordered;
		in right : Element[0..*] ordered;
		in key : String[1];
		in column : String[1];
		return result : Element[0..*] ordered;
	}

	/* Tree: the source rows arranged as a containment tree in pre-order, each
	 * row nested under the nearest row containing it — its nearest owner among
	 * the rows, or the individual whose part it is — at the depth the table
	 * indents it by; rows of ancestors join as intermediate levels where a
	 * source row nests under them. */
	calc def Tree {
		in source : Element[0..*] ordered;
		in ancestors : Element[0..*] ordered = null;
		return result : Element[0..*] ordered;
	}
}
